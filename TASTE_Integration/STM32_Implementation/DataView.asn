------------------------------------------------------------------------------
--                                                                          --
--          Copyright (C) 2022 Universidad Politécnica de Madrid            --
--                                                                          --
-- This is free software;  you can redistribute it  and/or modify it  under --
-- terms of the  GNU General Public License as published  by the Free Soft- --
-- ware  Foundation;  either version 3,  or (at your option) any later ver- --
-- sion.  This software is distributed in the hope  that it will be useful, --
-- but WITHOUT ANY WARRANTY;  without even the implied warranty of MERCHAN- --
-- TABILITY or FITNESS FOR A PARTICULAR PURPOSE. See the GNU General Public --
-- License for  more details.  You should have  received  a copy of the GNU --
-- General  Public  License  distributed  with  this  software;   see  file --
-- COPYING3.  If not, go to http://www.gnu.org/licenses for a complete copy --
-- of the license.                                                          --
--                                                                          --
------------------------------------------------------------------------------

STM32-IMPLEMENTATION-DATAVIEW DEFINITIONS ::=
BEGIN
    --IMPORTS T-UInt16 FROM TASTE-BasicTypes;
    --MyInteger ::= INTEGER (0 .. 10000)

     LED ::= ENUMERATED {
     	red-led,
	green-led,
	orange-led,
	blue-led
     }

    -------------------------
    -- Reusable data types --
    -------------------------
    T-UInt16 ::= INTEGER (0 .. 65535)
    -- NOTE: It is uint_32, since the GUI does not support UINT64
    T-UInt64 ::= INTEGER (0 .. 4294967295)
    T-Float  ::= REAL (-3.4e+38 .. 3.4e+38)

    Mission-Time ::= T-UInt64

    -------------------------------------------
    -- Data types used for the ACS component --
    -------------------------------------------
    -- Input types:
    T-B-b-T      ::= SEQUENCE (SIZE(15)) OF T-Float
    T-Omega      ::= SEQUENCE (SIZE(3))  OF T-Float
    T-MT-Working ::= SEQUENCE (SIZE(3))  OF T-Float

    -- Output types:
    T-Control    ::= SEQUENCE (SIZE(3))  OF T-Float

    -----------------------------------------------
    -- Data types used for the Sensors component --
    -----------------------------------------------
    Analog-Data ::= T-UInt16

    Analog-Data-Table ::= SEQUENCE {
        obc-t Analog-Data, -- OBC temperature
        obc-v Analog-Data  -- OBC supply voltages
    }

    -----------------------------------------------
    -- Data types used for the Storage component --
    -----------------------------------------------
    Satellite-State ::= SEQUENCE {
        timestamp   Mission-Time,
        data        Analog-Data-Table
    }

    -----------------------------------------------
    -- Data types used for the Manager component --
    -----------------------------------------------
    Operating-Mode ::= ENUMERATED {
        idle,
        coverage
    }

    -----------------------------------------
    -- TM and TC used by the TTC component --
    -----------------------------------------
    ------
    -- TC:
    ------
    TC-Type ::= ENUMERATED {
        open-link,
        close-link,
        request-hk
    }
    ------
    -- TM:
    ------
    TM-Message {Contents} ::=  SEQUENCE {
        tm-timestamp    Mission-Time,
        tm-payload      Contents
    }

    -- Hello
    TM-Hello ::= TM-Message {Satellite-State}

    -- Housekeeping
    hk-size INTEGER ::= 4
    TM-Housekeeping-Contents ::= SEQUENCE(SIZE(hk-size)) OF Satellite-State
    TM-Housekeeping ::= TM-Message {TM-Housekeeping-Contents}

    -- Mode
    TM-Mode ::= TM-Message {Operating-Mode}

    -- Error
    msg-size INTEGER ::= 80
    TM-Error-Contents ::= OCTET STRING (SIZE (0 .. msg-size))
    TM-Error ::= TM-Message {TM-Error-Contents}

    -- TM as a choice of TM types:
    TM-Type ::= CHOICE {
        hello   TM-Hello,
        hk      TM-Housekeeping,
        mode    TM-Mode,
        err     TM-Error
    }

    --------------------------
    -- TM Formatted for GUI --
    --------------------------
    Formatted-Data-Table ::= SEQUENCE {
        obc-t T-Float, -- OBC temperature Degrees Celsius
        obc-v T-Float  -- OBC supply voltages
    }

    Satellite-State-Formatted ::= SEQUENCE {
        timestamp   OCTET STRING (SIZE (0 .. msg-size)),
        data        Formatted-Data-Table
    }

    TM-Message-Formatted {Contents} ::=  SEQUENCE {
        tm-timestamp    OCTET STRING (SIZE (0 .. msg-size)),
        tm-payload      Contents
    }

    -- Hello
    TM-Hello-Formatted ::= TM-Message-Formatted {Satellite-State-Formatted}

    -- Housekeeping
    TM-Housekeeping-Formatted-Contents ::= SEQUENCE(SIZE(hk-size)) OF Satellite-State-Formatted
    TM-Housekeeping-Formatted ::= TM-Message-Formatted {TM-Housekeeping-Formatted-Contents}

    -- Mode
    TM-Mode-Formatted ::= TM-Message-Formatted {Operating-Mode}

    -- Error
    TM-Error-Formatted ::= TM-Message-Formatted {TM-Error-Contents}

    -- TM as a choice of TM Formatted types:
    TM-Type-Formatted ::= CHOICE {
        hello   TM-Hello-Formatted,
        hk      TM-Housekeeping-Formatted,
        mode    TM-Mode-Formatted,
        err     TM-Error-Formatted
    }

END
